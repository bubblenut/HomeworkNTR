RRCConnectionSetupTest DEFINITIONS AUTOMATIC TAGS ::= BEGIN
RRCConnectionSetup ::= SEQUENCE {
	rrc-TransactionIdentifier INTEGER (0..3),
	criticalExtensions CHOICE {
			c1 CHOICE {
					rrcConnectionSetup-r8 SEQUENCE {
							radioResourceConfigDedicated RadioResourceConfigDedicated
					}
			}
	}
}

RadioResourceConfigDedicated ::= SEQUENCE {
	srb-ToAddModList       SRB-ToAddModList OPTIONAL,
	drb-ToAddModList       DRB-ToAddModList OPTIONAL,
	drb-ToReleaseList      DRB-ToReleaseList OPTIONAL,
	rrcConnectionSetup-r8  RRCConnectionSetup-r8-IEs
}

SRB-ToAddModList ::= SEQUENCE (SIZE(1..2)) OF SRB-ToAddMod
DRB-ToAddModList ::= SEQUENCE (SIZE(1..32)) OF DRB-ToAddMod
DRB-ToReleaseList ::= SEQUENCE (SIZE(1..32)) OF DRB-Release

SRB-ToAddMod ::= SEQUENCE {
	srb-Identity INTEGER (1..2),
	rlc-Configuration RLC-Config
}

DRB-ToAddMod ::= SEQUENCE {
	eps-BearerIdentity INTEGER (1..15),
	drb-Identity INTEGER (1..32),
	pdcp-Configuration PDCP-Config
}

DRB-Release ::= SEQUENCE {
	drb-Identity INTEGER (1..32)
}
END
